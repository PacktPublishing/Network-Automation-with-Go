module arista-tunnel-tunnel-basic-types {
  yang-version 1;
  namespace "http://arista.com/yang/experimental/eos/arista-tunnel-tunnel-basic-types";
  prefix "arista-tunnel-tunnel-basic-types";

  import openconfig-extensions { prefix "oc-ext"; }
  organization
    "Arista Networks <http://arista.com/>";
  contact
    "Arista Networks <http://arista.com/>";
  description
    "Tunnel related types

    THIS YANG MODULE WAS GENERATED. DO NOT EDIT THIS FILE.";

  oc-ext:openconfig-version "1.0.0";

  revision "2021-10-20" {
    description
      "Version 1.0.0, generated on 2021-10-20";
    reference "1.0.0";
  }

  typedef tunnel-id {
    type uint64 {
      range "0..562949953421311";
    }
    default "0";
    description
      "Opaque identifier for a tunnel";
  }
}
