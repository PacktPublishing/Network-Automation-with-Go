submodule openconfig-hercules-platform-linecard {

  yang-version "1";

  belongs-to openconfig-hercules-platform {
    prefix "herc-platform";
  }

  // import some basic types
  import openconfig-platform { prefix oc-platform; }
  import openconfig-extensions { prefix oc-ext; }
  import openconfig-platform-linecard { prefix oc-platform-linecard; }

  // meta
  organization
    "OpenConfig Hercules Working Group";

  contact
    "openconfig-hercules@googlegroups.com";

  description
    "This submodule defines schema extensions to the
    OpenConfig platform model for a linecard component in the
    Hercules switch profile.";

  oc-ext:openconfig-version "0.2.0";

  revision 2018-06-01 {
    description
      "Initial version.";
    reference "0.2.0";
  }


  // grouping statements

  grouping hercules-linecard-config {
    description
      "Configuration data for linecard components";

    leaf slot-id {
      type string;
      description
        "Identifier for the slot (or chassis position) in which
        the linecard is installed.

        The SDN management system may need to assign the slot ID to
        the linecard via configuration.";
    }
  }

  // data definition statements

  // augment statements
  augment "/oc-platform:components/oc-platform:component/" +
    "oc-platform-linecard:linecard/oc-platform-linecard:config" {
    description
      "Extends the LINECARD component with additional configuration
      data";

    uses hercules-linecard-config;

  }
}
