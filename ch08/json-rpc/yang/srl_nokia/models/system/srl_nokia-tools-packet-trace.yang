module srl_nokia-tools-packet-trace {
  yang-version 1.1;
  namespace "urn:srl_nokia/tools-packet-trace";
  prefix srl_nokia-tools-packet-trace;

  import srl_nokia-tools-system {
    prefix srl-tools-system;
  }

  description
    "Model for operational commands on logging";

  revision 2019-11-30 {
    description
      "SRLinux 19.11.1";
  }

  grouping tools-packet-trace-top {
    description
      " Top-level grouping for packet-trace tools command";

    container packet-trace-base64 {
      presence "Configure tools system packet-trace-base64";
      description
        " Tools command to report the forwarding behavior for a specified test packet (packet specified in base64 format)";

      leaf interface {
        type string;

        description
          "References the configured name of the interface in which to inject the probe packet";
      }
      leaf packet {
        type binary;

        description
          "Packet content encoded in base64 string format";
      }
    }
  }

  augment "/srl-tools-system:system" {
    uses tools-packet-trace-top;
    // + packet-trace-base64 interface <if-name> packet <base64 encoded string>
  }
}
