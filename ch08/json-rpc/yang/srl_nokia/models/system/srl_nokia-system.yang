module srl_nokia-system {
  yang-version 1.1;

  // namespace

  namespace "urn:srl_nokia/system";
  prefix srl_nokia-system;

  import srl_nokia-extensions {
    prefix srl-ext;
  }
  import srl_nokia-common {
    prefix srl-comm;
  }

  description
    "This module defines configuration and operational state data
     related to system management

     Portions of this model reuse data definitions or structure from
     RFC 7317 - A YANG Data Model for System Management";

  revision 2020-06-30 {
    description
      "SRLinux 20.6.1";
  }
  revision 2019-11-30 {
    description
      "SRLinux 19.11.1";
  }

  container system {
    description
      "Enclosing container for system management";
    leaf-list features {
      srl-ext:first-released "20.6.1";
      config false;
      description
        "Features enabled on this platform";
      type srl-comm:name;
    }
    leaf-list trace-options {
      srl-ext:first-released "19.11.1";
      description
        "Management server trace options";
      type enumeration {
        enum request;
        enum response;
        enum common;
      }
    }
  }
}
