module srl_nokia-timezone {
  yang-version 1.1;
  namespace "urn:srl_nokia/timezone";
  prefix srl_nokia-timezone;

  organization
    "Nokia";
  description
    "This YANG module defines the srl-timezone typedef, which
     contains YANG definitions for tzdata timezones.";

  revision 2020-06-30 {
    description
      "SRLinux 20.6.1";
  }

  typedef tzdata-timezone {
    description
      "A timezone location as defined by the tzdata package";
    type enumeration {
      enum Africa/Abidjan {
        value 0;
      }
      enum Africa/Accra {
        value 1;
      }
      enum Africa/Addis_Ababa {
        value 2;
      }
      enum Africa/Algiers {
        value 3;
      }
      enum Africa/Asmara {
        value 4;
      }
      enum Africa/Bamako {
        value 5;
      }
      enum Africa/Bangui {
        value 6;
      }
      enum Africa/Banjul {
        value 7;
      }
      enum Africa/Bissau {
        value 8;
      }
      enum Africa/Blantyre {
        value 9;
      }
      enum Africa/Brazzaville {
        value 10;
      }
      enum Africa/Bujumbura {
        value 11;
      }
      enum Africa/Cairo {
        value 12;
      }
      enum Africa/Casablanca {
        value 13;
      }
      enum Africa/Ceuta {
        value 14;
        description
          "Ceuta, Melilla";
      }
      enum Africa/Conakry {
        value 15;
      }
      enum Africa/Dakar {
        value 16;
      }
      enum Africa/Dar_es_Salaam {
        value 17;
      }
      enum Africa/Djibouti {
        value 18;
      }
      enum Africa/Douala {
        value 19;
      }
      enum Africa/El_Aaiun {
        value 20;
      }
      enum Africa/Freetown {
        value 21;
      }
      enum Africa/Gaborone {
        value 22;
      }
      enum Africa/Harare {
        value 23;
      }
      enum Africa/Johannesburg {
        value 24;
      }
      enum Africa/Juba {
        value 25;
      }
      enum Africa/Kampala {
        value 26;
      }
      enum Africa/Khartoum {
        value 27;
      }
      enum Africa/Kigali {
        value 28;
      }
      enum Africa/Kinshasa {
        value 29;
        description
          "Dem. Rep. of Congo (west)";
      }
      enum Africa/Lagos {
        value 30;
      }
      enum Africa/Libreville {
        value 31;
      }
      enum Africa/Lome {
        value 32;
      }
      enum Africa/Luanda {
        value 33;
      }
      enum Africa/Lubumbashi {
        value 34;
        description
          "Dem. Rep. of Congo (east)";
      }
      enum Africa/Lusaka {
        value 35;
      }
      enum Africa/Malabo {
        value 36;
      }
      enum Africa/Maputo {
        value 37;
      }
      enum Africa/Maseru {
        value 38;
      }
      enum Africa/Mbabane {
        value 39;
      }
      enum Africa/Mogadishu {
        value 40;
      }
      enum Africa/Monrovia {
        value 41;
      }
      enum Africa/Nairobi {
        value 42;
      }
      enum Africa/Ndjamena {
        value 43;
      }
      enum Africa/Niamey {
        value 44;
      }
      enum Africa/Nouakchott {
        value 45;
      }
      enum Africa/Ouagadougou {
        value 46;
      }
      enum Africa/Porto-Novo {
        value 47;
      }
      enum Africa/Sao_Tome {
        value 48;
      }
      enum Africa/Tripoli {
        value 49;
      }
      enum Africa/Tunis {
        value 50;
      }
      enum Africa/Windhoek {
        value 51;
      }
      enum America/Adak {
        value 52;
        description
          "Aleutian Islands";
      }
      enum America/Anchorage {
        value 53;
        description
          "Alaska (most areas)";
      }
      enum America/Anguilla {
        value 54;
      }
      enum America/Antigua {
        value 55;
      }
      enum America/Araguaina {
        value 56;
        description
          "Tocantins";
      }
      enum America/Argentina/Buenos_Aires {
        value 57;
        description
          "Buenos Aires (BA, CF)";
      }
      enum America/Argentina/Catamarca {
        value 58;
        description
          "Catamarca (CT); Chubut (CH)";
      }
      enum America/Argentina/Cordoba {
        value 59;
        description
          "Argentina (most areas: CB, CC, CN, ER, FM, MN, SE, SF)";
      }
      enum America/Argentina/Jujuy {
        value 60;
        description
          "Jujuy (JY)";
      }
      enum America/Argentina/La_Rioja {
        value 61;
        description
          "La Rioja (LR)";
      }
      enum America/Argentina/Mendoza {
        value 62;
        description
          "Mendoza (MZ)";
      }
      enum America/Argentina/Rio_Gallegos {
        value 63;
        description
          "Santa Cruz (SC)";
      }
      enum America/Argentina/Salta {
        value 64;
        description
          "Salta (SA, LP, NQ, RN)";
      }
      enum America/Argentina/San_Juan {
        value 65;
        description
          "San Juan (SJ)";
      }
      enum America/Argentina/San_Luis {
        value 66;
        description
          "San Luis (SL)";
      }
      enum America/Argentina/Tucuman {
        value 67;
        description
          "Tucuman (TM)";
      }
      enum America/Argentina/Ushuaia {
        value 68;
        description
          "Tierra del Fuego (TF)";
      }
      enum America/Aruba {
        value 69;
      }
      enum America/Asuncion {
        value 70;
      }
      enum America/Atikokan {
        value 71;
        description
          "EST - ON (Atikokan); NU (Coral H)";
      }
      enum America/Bahia {
        value 72;
        description
          "Bahia";
      }
      enum America/Bahia_Banderas {
        value 73;
        description
          "Central Time - Bahia de Banderas";
      }
      enum America/Barbados {
        value 74;
      }
      enum America/Belem {
        value 75;
        description
          "Para (east); Amapa";
      }
      enum America/Belize {
        value 76;
      }
      enum America/Blanc-Sablon {
        value 77;
        description
          "AST - QC (Lower North Shore)";
      }
      enum America/Boa_Vista {
        value 78;
        description
          "Roraima";
      }
      enum America/Bogota {
        value 79;
      }
      enum America/Boise {
        value 80;
        description
          "Mountain - ID (south); OR (east)";
      }
      enum America/Cambridge_Bay {
        value 81;
        description
          "Mountain - NU (west)";
      }
      enum America/Campo_Grande {
        value 82;
        description
          "Mato Grosso do Sul";
      }
      enum America/Cancun {
        value 83;
        description
          "Eastern Standard Time - Quintana Roo";
      }
      enum America/Caracas {
        value 84;
      }
      enum America/Cayenne {
        value 85;
      }
      enum America/Cayman {
        value 86;
      }
      enum America/Chicago {
        value 87;
        description
          "Central (most areas)";
      }
      enum America/Chihuahua {
        value 88;
        description
          "Mountain Time - Chihuahua (most areas)";
      }
      enum America/Costa_Rica {
        value 89;
      }
      enum America/Creston {
        value 90;
        description
          "MST - BC (Creston)";
      }
      enum America/Cuiaba {
        value 91;
        description
          "Mato Grosso";
      }
      enum America/Curacao {
        value 92;
      }
      enum America/Danmarkshavn {
        value 93;
        description
          "National Park (east coast)";
      }
      enum America/Dawson {
        value 94;
        description
          "Pacific - Yukon (north)";
      }
      enum America/Dawson_Creek {
        value 95;
        description
          "MST - BC (Dawson Cr, Ft St John)";
      }
      enum America/Denver {
        value 96;
        description
          "Mountain (most areas)";
      }
      enum America/Detroit {
        value 97;
        description
          "Eastern - MI (most areas)";
      }
      enum America/Dominica {
        value 98;
      }
      enum America/Edmonton {
        value 99;
        description
          "Mountain - AB; BC (E); SK (W)";
      }
      enum America/Eirunepe {
        value 100;
        description
          "Amazonas (west)";
      }
      enum America/El_Salvador {
        value 101;
      }
      enum America/Fort_Nelson {
        value 102;
        description
          "MST - BC (Ft Nelson)";
      }
      enum America/Fortaleza {
        value 103;
        description
          "Brazil (northeast: MA, PI, CE, RN, PB)";
      }
      enum America/Glace_Bay {
        value 104;
        description
          "Atlantic - NS (Cape Breton)";
      }
      enum America/Godthab {
        value 105;
        description
          "Greenland (most areas)";
      }
      enum America/Goose_Bay {
        value 106;
        description
          "Atlantic - Labrador (most areas)";
      }
      enum America/Grand_Turk {
        value 107;
      }
      enum America/Grenada {
        value 108;
      }
      enum America/Guadeloupe {
        value 109;
      }
      enum America/Guatemala {
        value 110;
      }
      enum America/Guayaquil {
        value 111;
        description
          "Ecuador (mainland)";
      }
      enum America/Guyana {
        value 112;
      }
      enum America/Halifax {
        value 113;
        description
          "Atlantic - NS (most areas); PE";
      }
      enum America/Havana {
        value 114;
      }
      enum America/Hermosillo {
        value 115;
        description
          "Mountain Standard Time - Sonora";
      }
      enum America/Indiana/Indianapolis {
        value 116;
        description
          "Eastern - IN (most areas)";
      }
      enum America/Indiana/Knox {
        value 117;
        description
          "Central - IN (Starke)";
      }
      enum America/Indiana/Marengo {
        value 118;
        description
          "Eastern - IN (Crawford)";
      }
      enum America/Indiana/Petersburg {
        value 119;
        description
          "Eastern - IN (Pike)";
      }
      enum America/Indiana/Tell_City {
        value 120;
        description
          "Central - IN (Perry)";
      }
      enum America/Indiana/Vevay {
        value 121;
        description
          "Eastern - IN (Switzerland)";
      }
      enum America/Indiana/Vincennes {
        value 122;
        description
          "Eastern - IN (Da, Du, K, Mn)";
      }
      enum America/Indiana/Winamac {
        value 123;
        description
          "Eastern - IN (Pulaski)";
      }
      enum America/Inuvik {
        value 124;
        description
          "Mountain - NT (west)";
      }
      enum America/Iqaluit {
        value 125;
        description
          "Eastern - NU (most east areas)";
      }
      enum America/Jamaica {
        value 126;
      }
      enum America/Juneau {
        value 127;
        description
          "Alaska - Juneau area";
      }
      enum America/Kentucky/Louisville {
        value 128;
        description
          "Eastern - KY (Louisville area)";
      }
      enum America/Kentucky/Monticello {
        value 129;
        description
          "Eastern - KY (Wayne)";
      }
      enum America/Kralendijk {
        value 130;
      }
      enum America/La_Paz {
        value 131;
      }
      enum America/Lima {
        value 132;
      }
      enum America/Los_Angeles {
        value 133;
        description
          "Pacific";
      }
      enum America/Lower_Princes {
        value 134;
      }
      enum America/Maceio {
        value 135;
        description
          "Alagoas, Sergipe";
      }
      enum America/Managua {
        value 136;
      }
      enum America/Manaus {
        value 137;
        description
          "Amazonas (east)";
      }
      enum America/Marigot {
        value 138;
      }
      enum America/Martinique {
        value 139;
      }
      enum America/Matamoros {
        value 140;
        description
          "Central Time US - Coahuila, Nuevo Leon, Tamaulipas (US border)";
      }
      enum America/Mazatlan {
        value 141;
        description
          "Mountain Time - Baja California Sur, Nayarit, Sinaloa";
      }
      enum America/Menominee {
        value 142;
        description
          "Central - MI (Wisconsin border)";
      }
      enum America/Merida {
        value 143;
        description
          "Central Time - Campeche, Yucatan";
      }
      enum America/Metlakatla {
        value 144;
        description
          "Alaska - Annette Island";
      }
      enum America/Mexico_City {
        value 145;
        description
          "Central Time";
      }
      enum America/Miquelon {
        value 146;
      }
      enum America/Moncton {
        value 147;
        description
          "Atlantic - New Brunswick";
      }
      enum America/Monterrey {
        value 148;
        description
          "Central Time - Durango; Coahuila, Nuevo Leon, Tamaulipas (most areas)";
      }
      enum America/Montevideo {
        value 149;
      }
      enum America/Montserrat {
        value 150;
      }
      enum America/Nassau {
        value 151;
      }
      enum America/New_York {
        value 152;
        description
          "Eastern (most areas)";
      }
      enum America/Nipigon {
        value 153;
        description
          "Eastern - ON, QC (no DST 1967-73)";
      }
      enum America/Nome {
        value 154;
        description
          "Alaska (west)";
      }
      enum America/Noronha {
        value 155;
        description
          "Atlantic islands";
      }
      enum America/North_Dakota/Beulah {
        value 156;
        description
          "Central - ND (Mercer)";
      }
      enum America/North_Dakota/Center {
        value 157;
        description
          "Central - ND (Oliver)";
      }
      enum America/North_Dakota/New_Salem {
        value 158;
        description
          "Central - ND (Morton rural)";
      }
      enum America/Ojinaga {
        value 159;
        description
          "Mountain Time US - Chihuahua (US border)";
      }
      enum America/Panama {
        value 160;
      }
      enum America/Pangnirtung {
        value 161;
        description
          "Eastern - NU (Pangnirtung)";
      }
      enum America/Paramaribo {
        value 162;
      }
      enum America/Phoenix {
        value 163;
        description
          "MST - Arizona (except Navajo)";
      }
      enum America/Port-au-Prince {
        value 164;
      }
      enum America/Port_of_Spain {
        value 165;
      }
      enum America/Porto_Velho {
        value 166;
        description
          "Rondonia";
      }
      enum America/Puerto_Rico {
        value 167;
      }
      enum America/Punta_Arenas {
        value 168;
        description
          "Region of Magallanes";
      }
      enum America/Rainy_River {
        value 169;
        description
          "Central - ON (Rainy R, Ft Frances)";
      }
      enum America/Rankin_Inlet {
        value 170;
        description
          "Central - NU (central)";
      }
      enum America/Recife {
        value 171;
        description
          "Pernambuco";
      }
      enum America/Regina {
        value 172;
        description
          "CST - SK (most areas)";
      }
      enum America/Resolute {
        value 173;
        description
          "Central - NU (Resolute)";
      }
      enum America/Rio_Branco {
        value 174;
        description
          "Acre";
      }
      enum America/Santarem {
        value 175;
        description
          "Para (west)";
      }
      enum America/Santiago {
        value 176;
        description
          "Chile (most areas)";
      }
      enum America/Santo_Domingo {
        value 177;
      }
      enum America/Sao_Paulo {
        value 178;
        description
          "Brazil (southeast: GO, DF, MG, ES, RJ, SP, PR, SC, RS)";
      }
      enum America/Scoresbysund {
        value 179;
        description
          "Scoresbysund/Ittoqqortoormiit";
      }
      enum America/Sitka {
        value 180;
        description
          "Alaska - Sitka area";
      }
      enum America/St_Barthelemy {
        value 181;
      }
      enum America/St_Johns {
        value 182;
        description
          "Newfoundland; Labrador (southeast)";
      }
      enum America/St_Kitts {
        value 183;
      }
      enum America/St_Lucia {
        value 184;
      }
      enum America/St_Thomas {
        value 185;
      }
      enum America/St_Vincent {
        value 186;
      }
      enum America/Swift_Current {
        value 187;
        description
          "CST - SK (midwest)";
      }
      enum America/Tegucigalpa {
        value 188;
      }
      enum America/Thule {
        value 189;
        description
          "Thule/Pituffik";
      }
      enum America/Thunder_Bay {
        value 190;
        description
          "Eastern - ON (Thunder Bay)";
      }
      enum America/Tijuana {
        value 191;
        description
          "Pacific Time US - Baja California";
      }
      enum America/Toronto {
        value 192;
        description
          "Eastern - ON, QC (most areas)";
      }
      enum America/Tortola {
        value 193;
      }
      enum America/Vancouver {
        value 194;
        description
          "Pacific - BC (most areas)";
      }
      enum America/Whitehorse {
        value 195;
        description
          "Pacific - Yukon (south)";
      }
      enum America/Winnipeg {
        value 196;
        description
          "Central - ON (west); Manitoba";
      }
      enum America/Yakutat {
        value 197;
        description
          "Alaska - Yakutat";
      }
      enum America/Yellowknife {
        value 198;
        description
          "Mountain - NT (central)";
      }
      enum Antarctica/Casey {
        value 199;
        description
          "Casey";
      }
      enum Antarctica/Davis {
        value 200;
        description
          "Davis";
      }
      enum Antarctica/DumontDUrville {
        value 201;
        description
          "Dumont-d'Urville";
      }
      enum Antarctica/Macquarie {
        value 202;
        description
          "Macquarie Island";
      }
      enum Antarctica/Mawson {
        value 203;
        description
          "Mawson";
      }
      enum Antarctica/McMurdo {
        value 204;
        description
          "New Zealand time - McMurdo, South Pole";
      }
      enum Antarctica/Palmer {
        value 205;
        description
          "Palmer";
      }
      enum Antarctica/Rothera {
        value 206;
        description
          "Rothera";
      }
      enum Antarctica/Syowa {
        value 207;
        description
          "Syowa";
      }
      enum Antarctica/Troll {
        value 208;
        description
          "Troll";
      }
      enum Antarctica/Vostok {
        value 209;
        description
          "Vostok";
      }
      enum Arctic/Longyearbyen {
        value 210;
      }
      enum Asia/Aden {
        value 211;
      }
      enum Asia/Almaty {
        value 212;
        description
          "Kazakhstan (most areas)";
      }
      enum Asia/Amman {
        value 213;
      }
      enum Asia/Anadyr {
        value 214;
        description
          "MSK+09 - Bering Sea";
      }
      enum Asia/Aqtau {
        value 215;
        description
          "Mangghystau/Mankistau";
      }
      enum Asia/Aqtobe {
        value 216;
        description
          "Aqtobe/Aktobe";
      }
      enum Asia/Ashgabat {
        value 217;
      }
      enum Asia/Atyrau {
        value 218;
        description
          "Atyrau/Atirau/Gur'yev";
      }
      enum Asia/Baghdad {
        value 219;
      }
      enum Asia/Bahrain {
        value 220;
      }
      enum Asia/Baku {
        value 221;
      }
      enum Asia/Bangkok {
        value 222;
      }
      enum Asia/Barnaul {
        value 223;
        description
          "MSK+04 - Altai";
      }
      enum Asia/Beirut {
        value 224;
      }
      enum Asia/Bishkek {
        value 225;
      }
      enum Asia/Brunei {
        value 226;
      }
      enum Asia/Chita {
        value 227;
        description
          "MSK+06 - Zabaykalsky";
      }
      enum Asia/Choibalsan {
        value 228;
        description
          "Dornod, Sukhbaatar";
      }
      enum Asia/Colombo {
        value 229;
      }
      enum Asia/Damascus {
        value 230;
      }
      enum Asia/Dhaka {
        value 231;
      }
      enum Asia/Dili {
        value 232;
      }
      enum Asia/Dubai {
        value 233;
      }
      enum Asia/Dushanbe {
        value 234;
      }
      enum Asia/Famagusta {
        value 235;
        description
          "Northern Cyprus";
      }
      enum Asia/Gaza {
        value 236;
        description
          "Gaza Strip";
      }
      enum Asia/Hebron {
        value 237;
        description
          "West Bank";
      }
      enum Asia/Ho_Chi_Minh {
        value 238;
      }
      enum Asia/Hong_Kong {
        value 239;
      }
      enum Asia/Hovd {
        value 240;
        description
          "Bayan-Olgiy, Govi-Altai, Hovd, Uvs, Zavkhan";
      }
      enum Asia/Irkutsk {
        value 241;
        description
          "MSK+05 - Irkutsk, Buryatia";
      }
      enum Asia/Jakarta {
        value 242;
        description
          "Java, Sumatra";
      }
      enum Asia/Jayapura {
        value 243;
        description
          "New Guinea (West Papua / Irian Jaya); Malukus/Moluccas";
      }
      enum Asia/Jerusalem {
        value 244;
      }
      enum Asia/Kabul {
        value 245;
      }
      enum Asia/Kamchatka {
        value 246;
        description
          "MSK+09 - Kamchatka";
      }
      enum Asia/Karachi {
        value 247;
      }
      enum Asia/Kathmandu {
        value 248;
      }
      enum Asia/Khandyga {
        value 249;
        description
          "MSK+06 - Tomponsky, Ust-Maysky";
      }
      enum Asia/Kolkata {
        value 250;
      }
      enum Asia/Krasnoyarsk {
        value 251;
        description
          "MSK+04 - Krasnoyarsk area";
      }
      enum Asia/Kuala_Lumpur {
        value 252;
        description
          "Malaysia (peninsula)";
      }
      enum Asia/Kuching {
        value 253;
        description
          "Sabah, Sarawak";
      }
      enum Asia/Kuwait {
        value 254;
      }
      enum Asia/Macau {
        value 255;
      }
      enum Asia/Magadan {
        value 256;
        description
          "MSK+08 - Magadan";
      }
      enum Asia/Makassar {
        value 257;
        description
          "Borneo (east, south); Sulawesi/Celebes, Bali, Nusa Tengarra; Timor (west)";
      }
      enum Asia/Manila {
        value 258;
      }
      enum Asia/Muscat {
        value 259;
      }
      enum Asia/Nicosia {
        value 260;
        description
          "Cyprus (most areas)";
      }
      enum Asia/Novokuznetsk {
        value 261;
        description
          "MSK+04 - Kemerovo";
      }
      enum Asia/Novosibirsk {
        value 262;
        description
          "MSK+04 - Novosibirsk";
      }
      enum Asia/Omsk {
        value 263;
        description
          "MSK+03 - Omsk";
      }
      enum Asia/Oral {
        value 264;
        description
          "West Kazakhstan";
      }
      enum Asia/Phnom_Penh {
        value 265;
      }
      enum Asia/Pontianak {
        value 266;
        description
          "Borneo (west, central)";
      }
      enum Asia/Pyongyang {
        value 267;
      }
      enum Asia/Qatar {
        value 268;
      }
      enum Asia/Qostanay {
        value 269;
        description
          "Qostanay/Kostanay/Kustanay";
      }
      enum Asia/Qyzylorda {
        value 270;
        description
          "Qyzylorda/Kyzylorda/Kzyl-Orda";
      }
      enum Asia/Riyadh {
        value 271;
      }
      enum Asia/Sakhalin {
        value 272;
        description
          "MSK+08 - Sakhalin Island";
      }
      enum Asia/Samarkand {
        value 273;
        description
          "Uzbekistan (west)";
      }
      enum Asia/Seoul {
        value 274;
      }
      enum Asia/Shanghai {
        value 275;
        description
          "Beijing Time";
      }
      enum Asia/Singapore {
        value 276;
      }
      enum Asia/Srednekolymsk {
        value 277;
        description
          "MSK+08 - Sakha (E); North Kuril Is";
      }
      enum Asia/Taipei {
        value 278;
      }
      enum Asia/Tashkent {
        value 279;
        description
          "Uzbekistan (east)";
      }
      enum Asia/Tbilisi {
        value 280;
      }
      enum Asia/Tehran {
        value 281;
      }
      enum Asia/Thimphu {
        value 282;
      }
      enum Asia/Tokyo {
        value 283;
      }
      enum Asia/Tomsk {
        value 284;
        description
          "MSK+04 - Tomsk";
      }
      enum Asia/Ulaanbaatar {
        value 285;
        description
          "Mongolia (most areas)";
      }
      enum Asia/Urumqi {
        value 286;
        description
          "Xinjiang Time";
      }
      enum Asia/Ust-Nera {
        value 287;
        description
          "MSK+07 - Oymyakonsky";
      }
      enum Asia/Vientiane {
        value 288;
      }
      enum Asia/Vladivostok {
        value 289;
        description
          "MSK+07 - Amur River";
      }
      enum Asia/Yakutsk {
        value 290;
        description
          "MSK+06 - Lena River";
      }
      enum Asia/Yangon {
        value 291;
      }
      enum Asia/Yekaterinburg {
        value 292;
        description
          "MSK+02 - Urals";
      }
      enum Asia/Yerevan {
        value 293;
      }
      enum Atlantic/Azores {
        value 294;
        description
          "Azores";
      }
      enum Atlantic/Bermuda {
        value 295;
      }
      enum Atlantic/Canary {
        value 296;
        description
          "Canary Islands";
      }
      enum Atlantic/Cape_Verde {
        value 297;
      }
      enum Atlantic/Faroe {
        value 298;
      }
      enum Atlantic/Madeira {
        value 299;
        description
          "Madeira Islands";
      }
      enum Atlantic/Reykjavik {
        value 300;
      }
      enum Atlantic/South_Georgia {
        value 301;
      }
      enum Atlantic/St_Helena {
        value 302;
      }
      enum Atlantic/Stanley {
        value 303;
      }
      enum Australia/Adelaide {
        value 304;
        description
          "South Australia";
      }
      enum Australia/Brisbane {
        value 305;
        description
          "Queensland (most areas)";
      }
      enum Australia/Broken_Hill {
        value 306;
        description
          "New South Wales (Yancowinna)";
      }
      enum Australia/Currie {
        value 307;
        description
          "Tasmania (King Island)";
      }
      enum Australia/Darwin {
        value 308;
        description
          "Northern Territory";
      }
      enum Australia/Eucla {
        value 309;
        description
          "Western Australia (Eucla)";
      }
      enum Australia/Hobart {
        value 310;
        description
          "Tasmania (most areas)";
      }
      enum Australia/Lindeman {
        value 311;
        description
          "Queensland (Whitsunday Islands)";
      }
      enum Australia/Lord_Howe {
        value 312;
        description
          "Lord Howe Island";
      }
      enum Australia/Melbourne {
        value 313;
        description
          "Victoria";
      }
      enum Australia/Perth {
        value 314;
        description
          "Western Australia (most areas)";
      }
      enum Australia/Sydney {
        value 315;
        description
          "New South Wales (most areas)";
      }
      enum Europe/Amsterdam {
        value 316;
      }
      enum Europe/Andorra {
        value 317;
      }
      enum Europe/Astrakhan {
        value 318;
        description
          "MSK+01 - Astrakhan";
      }
      enum Europe/Athens {
        value 319;
      }
      enum Europe/Belgrade {
        value 320;
      }
      enum Europe/Berlin {
        value 321;
        description
          "Germany (most areas)";
      }
      enum Europe/Bratislava {
        value 322;
      }
      enum Europe/Brussels {
        value 323;
      }
      enum Europe/Bucharest {
        value 324;
      }
      enum Europe/Budapest {
        value 325;
      }
      enum Europe/Busingen {
        value 326;
        description
          "Busingen";
      }
      enum Europe/Chisinau {
        value 327;
      }
      enum Europe/Copenhagen {
        value 328;
      }
      enum Europe/Dublin {
        value 329;
      }
      enum Europe/Gibraltar {
        value 330;
      }
      enum Europe/Guernsey {
        value 331;
      }
      enum Europe/Helsinki {
        value 332;
      }
      enum Europe/Isle_of_Man {
        value 333;
      }
      enum Europe/Istanbul {
        value 334;
      }
      enum Europe/Jersey {
        value 335;
      }
      enum Europe/Kaliningrad {
        value 336;
        description
          "MSK-01 - Kaliningrad";
      }
      enum Europe/Kiev {
        value 337;
        description
          "Ukraine (most areas)";
      }
      enum Europe/Kirov {
        value 338;
        description
          "MSK+00 - Kirov";
      }
      enum Europe/Lisbon {
        value 339;
        description
          "Portugal (mainland)";
      }
      enum Europe/Ljubljana {
        value 340;
      }
      enum Europe/London {
        value 341;
      }
      enum Europe/Luxembourg {
        value 342;
      }
      enum Europe/Madrid {
        value 343;
        description
          "Spain (mainland)";
      }
      enum Europe/Malta {
        value 344;
      }
      enum Europe/Mariehamn {
        value 345;
      }
      enum Europe/Minsk {
        value 346;
      }
      enum Europe/Monaco {
        value 347;
      }
      enum Europe/Moscow {
        value 348;
        description
          "MSK+00 - Moscow area";
      }
      enum Europe/Oslo {
        value 349;
      }
      enum Europe/Paris {
        value 350;
      }
      enum Europe/Podgorica {
        value 351;
      }
      enum Europe/Prague {
        value 352;
      }
      enum Europe/Riga {
        value 353;
      }
      enum Europe/Rome {
        value 354;
      }
      enum Europe/Samara {
        value 355;
        description
          "MSK+01 - Samara, Udmurtia";
      }
      enum Europe/San_Marino {
        value 356;
      }
      enum Europe/Sarajevo {
        value 357;
      }
      enum Europe/Saratov {
        value 358;
        description
          "MSK+01 - Saratov";
      }
      enum Europe/Simferopol {
        value 359;
        description
          "MSK+00 - Crimea";
      }
      enum Europe/Skopje {
        value 360;
      }
      enum Europe/Sofia {
        value 361;
      }
      enum Europe/Stockholm {
        value 362;
      }
      enum Europe/Tallinn {
        value 363;
      }
      enum Europe/Tirane {
        value 364;
      }
      enum Europe/Ulyanovsk {
        value 365;
        description
          "MSK+01 - Ulyanovsk";
      }
      enum Europe/Uzhgorod {
        value 366;
        description
          "Ruthenia";
      }
      enum Europe/Vaduz {
        value 367;
      }
      enum Europe/Vatican {
        value 368;
      }
      enum Europe/Vienna {
        value 369;
      }
      enum Europe/Vilnius {
        value 370;
      }
      enum Europe/Volgograd {
        value 371;
        description
          "MSK+01 - Volgograd";
      }
      enum Europe/Warsaw {
        value 372;
      }
      enum Europe/Zagreb {
        value 373;
      }
      enum Europe/Zaporozhye {
        value 374;
        description
          "Zaporozh'ye/Zaporizhia; Lugansk/Luhansk (east)";
      }
      enum Europe/Zurich {
        value 375;
      }
      enum Indian/Antananarivo {
        value 376;
      }
      enum Indian/Chagos {
        value 377;
      }
      enum Indian/Christmas {
        value 378;
      }
      enum Indian/Cocos {
        value 379;
      }
      enum Indian/Comoro {
        value 380;
      }
      enum Indian/Kerguelen {
        value 381;
      }
      enum Indian/Mahe {
        value 382;
      }
      enum Indian/Maldives {
        value 383;
      }
      enum Indian/Mauritius {
        value 384;
      }
      enum Indian/Mayotte {
        value 385;
      }
      enum Indian/Reunion {
        value 386;
      }
      enum Pacific/Apia {
        value 387;
      }
      enum Pacific/Auckland {
        value 388;
        description
          "New Zealand (most areas)";
      }
      enum Pacific/Bougainville {
        value 389;
        description
          "Bougainville";
      }
      enum Pacific/Chatham {
        value 390;
        description
          "Chatham Islands";
      }
      enum Pacific/Chuuk {
        value 391;
        description
          "Chuuk/Truk, Yap";
      }
      enum Pacific/Easter {
        value 392;
        description
          "Easter Island";
      }
      enum Pacific/Efate {
        value 393;
      }
      enum Pacific/Enderbury {
        value 394;
        description
          "Phoenix Islands";
      }
      enum Pacific/Fakaofo {
        value 395;
      }
      enum Pacific/Fiji {
        value 396;
      }
      enum Pacific/Funafuti {
        value 397;
      }
      enum Pacific/Galapagos {
        value 398;
        description
          "Galapagos Islands";
      }
      enum Pacific/Gambier {
        value 399;
        description
          "Gambier Islands";
      }
      enum Pacific/Guadalcanal {
        value 400;
      }
      enum Pacific/Guam {
        value 401;
      }
      enum Pacific/Honolulu {
        value 402;
        description
          "Hawaii";
      }
      enum Pacific/Kiritimati {
        value 403;
        description
          "Line Islands";
      }
      enum Pacific/Kosrae {
        value 404;
        description
          "Kosrae";
      }
      enum Pacific/Kwajalein {
        value 405;
        description
          "Kwajalein";
      }
      enum Pacific/Majuro {
        value 406;
        description
          "Marshall Islands (most areas)";
      }
      enum Pacific/Marquesas {
        value 407;
        description
          "Marquesas Islands";
      }
      enum Pacific/Midway {
        value 408;
        description
          "Midway Islands";
      }
      enum Pacific/Nauru {
        value 409;
      }
      enum Pacific/Niue {
        value 410;
      }
      enum Pacific/Norfolk {
        value 411;
      }
      enum Pacific/Noumea {
        value 412;
      }
      enum Pacific/Pago_Pago {
        value 413;
      }
      enum Pacific/Palau {
        value 414;
      }
      enum Pacific/Pitcairn {
        value 415;
      }
      enum Pacific/Pohnpei {
        value 416;
        description
          "Pohnpei/Ponape";
      }
      enum Pacific/Port_Moresby {
        value 417;
        description
          "Papua New Guinea (most areas)";
      }
      enum Pacific/Rarotonga {
        value 418;
      }
      enum Pacific/Saipan {
        value 419;
      }
      enum Pacific/Tahiti {
        value 420;
        description
          "Society Islands";
      }
      enum Pacific/Tarawa {
        value 421;
        description
          "Gilbert Islands";
      }
      enum Pacific/Tongatapu {
        value 422;
      }
      enum Pacific/Wake {
        value 423;
        description
          "Wake Island";
      }
      enum Pacific/Wallis {
        value 424;
      }
      enum UTC {
        value 425;
      }
    }
  }
}
