module srl_nokia-bridge-table-mac-learning-entries {

  yang-version "1.1";

  // namespace
  namespace "urn:srl_nokia/network-instance/bridge-table/mac-learning/mac-learning-entries";

  prefix "srl_nokia-bridge-table-mac-learning-entries";

  import srl_nokia-common { prefix srl_nokia-comm; }
  import srl_nokia-extensions { prefix srl_nokia-ext; }
  import srl_nokia-network-instance { prefix srl_nokia-netinst; }

  description
    "This yang file gives a description of bridge table configuration.";

  revision 2021-03-31 {
    description
      "SRLinux 21.3.1";
  }
  revision 2020-06-30 {
    description
      "SRLinux 20.6.1";
  }

  grouping bridge-table-mac-learning-entries-top {
    container learnt-entries {
      config false;
      list mac {
        config false;
        key "address";
        description "macs learnt on the bridging instance";
        leaf address {
          type srl_nokia-comm:mac-address;
          srl_nokia-ext:show-importance "high";
        }

        leaf destination {
          type string;
          srl_nokia-ext:show-importance "high";
          description
            "the name of the subinterface where the mac is learnt against.";
        }

        leaf last-update {
          type srl_nokia-comm:date-and-time-delta;
          srl_nokia-ext:show-importance "high";
          description
            "The date and time of the last update of this learnt mac";
        }

        leaf aging {
          type union {
            type uint64;
            type enumeration {
              enum "disabled"  { value -1; }
            }
          }
          units "seconds";
          srl_nokia-ext:show-importance "high";
          description 
            "remaining age time for learnt macs";
        }     
      }   
    }
  }

  augment "/srl_nokia-netinst:network-instance/srl_nokia-netinst:bridge-table/srl_nokia-netinst:mac-learning" {
    uses bridge-table-mac-learning-entries-top;
  }
}
