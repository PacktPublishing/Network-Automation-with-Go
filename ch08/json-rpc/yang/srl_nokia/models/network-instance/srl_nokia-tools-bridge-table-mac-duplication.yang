module srl_nokia-tools-bridge-table-mac-duplication {
  yang-version 1.1;
  namespace "urn:srl_nokia/network-instance/tools-bridge-table/tools-mac-duplication";
  prefix srl_nokia-tools-bridge-table-mac-duplication;

  import srl_nokia-common {
    prefix srl_nokia-comm;
  }

  import srl_nokia-tools-network-instance { 
    prefix srl_nokia-tools-netinst; 
  }

  description
    "Model for network-instance bridge-table mac duplication operational commands";

  revision 2020-06-30 {
    description
      "SRLinux 20.6.1";
  }

  grouping tools-bridge-table-mac-duplication-top {
    container mac-duplication {
      presence "bridge table mac duplication";
      leaf delete-macs-type {
        type enumeration {
          enum "all";
          enum "blackhole-only";
        }
        description
          "Type of duplicate mac entries to delete.";
      }
      container duplicate-entries {
        list mac {
          key "address";
          description "macs learnt on the bridging instance";
          leaf address {
            type srl_nokia-comm:mac-address;
          }
          leaf delete-mac {
            type empty;
            description
              "delete the duplicate mac address.";
          }
        }
      }
    }
  }
  augment "/srl_nokia-tools-netinst:network-instance/srl_nokia-tools-netinst:bridge-table" {
      uses tools-bridge-table-mac-duplication-top;
  }
}
