module srl_nokia-lacp {
  yang-version 1.1;

  // namespace
  namespace "urn:srl_nokia/lacp";

  prefix "srl_nokia-lacp";

	//import 
	
  //import srl_nokia-extensions { prefix srl_nokia-ext; }
  import srl_nokia-interfaces { prefix srl_nokia-if; }
  import srl_nokia-common { prefix srl_nokia-comm; }
  import srl_nokia-interfaces-lag { prefix srl_nokia-if-lag; }
  import srl_nokia-system { prefix srl_nokia-system; }
  import srl_nokia-features { prefix srl_nokia-feat; }

  description
    "Model for managing LACP

     This model describes management of LACP parameters under SRL";

  // identity statements

  // typedef statements

  revision 2021-03-31 {
    description
      "SRLinux 21.3.1";
  }
  revision 2020-06-30 {
    description
      "SRLinux 20.6.1";
  }

  typedef lacp-activity-type {
    type enumeration {
      enum ACTIVE {
        description
          "Interface is an active member, i.e., will detect and
          maintain aggregates";
      }
      enum PASSIVE {
        description
          "Interface is a passive member, i.e., it participates
          with an active partner";
      }
    }
    description
      "Describes the LACP membership type, active or passive, of the
      interface in the aggregate";
    reference "IEEE 802.1AX-2008";
  }

  typedef lacp-timeout-type {
    type enumeration {
      enum LONG {
        description
          "Participant wishes to use long timeouts to detect
          status of the aggregate, i.e., will expect less frequent
          transmissions. Long timeout is 90 seconds.";
      }
      enum SHORT {
        description
          "Participant wishes to use short timeouts, i.e., expects
          frequent transmissions to aggressively detect status
          changes. Short timeout is 3 seconds.";
      }
    }
    description
      "Type of timeout used, short or long, by LACP participants";
    reference "IEEE 802.1AX-2008";
  }

  typedef lacp-synchronization-type {
    type enumeration {
      enum IN_SYNC {
        description
          "Participant is in sync with the system id and key
          transmitted";
      }
      enum OUT_SYNC {
        description
          "Participant is not in sync with the system id and key
          transmitted";
      }
    }
    description
      "Indicates LACP synchronization state of participant";
    reference "IEEE 802.1AX-2008";
  }

  typedef lacp-period-type {
    type enumeration {
      enum FAST {
        description "Send LACP packets every second";
      }
      enum SLOW {
        description "Send LACP packets every 30 seconds";
      }
    }
    description
      "Defines the period options for the time between sending
      LACP messages";
    reference "IEEE 802.3ad";
  }

	// Groupings
	
	grouping lag-lacp-members-state {
    description
      "Operational status data for the member interfaces";

    leaf activity {
      type lacp-activity-type;
      description "Indicates participant is active or passive";
    }

    leaf timeout {
      type lacp-timeout-type;
      description
        "The timeout type (short or long) used by the
        participant";
    }

    leaf synchronization {
      type lacp-synchronization-type;
      description
        "Indicates whether the participant is in-sync or
        out-of-sync";
    }

    leaf aggregatable {
      type boolean;
      description
        "A true value indicates that the participant will allow
        the link to be used as part of the aggregate. A false
        value indicates the link should be used as an individual
        link";
    }

    leaf collecting {
      type boolean;
      description
        "If true, the participant is collecting incoming frames
        on the link, otherwise false";
    }

    leaf distributing {
      type boolean;
      description
        "When true, the participant is distributing outgoing
        frames; when false, distribution is disabled";
    }

    leaf system-id {
      type srl_nokia-comm:mac-address;
      description
        "MAC address that defines the local system ID for the
        aggregate interface";
    }

    leaf oper-key {
      type uint16;
      description
        "Current operational value of the key for the aggregate
        interface";
    }

    leaf partner-id {
      type srl_nokia-comm:mac-address;
      description
        "MAC address representing the protocol partner's interface
        system ID";
    }

    leaf partner-key {
      type uint16;
      description
        "Operational value of the protocol partner's key";
    }

    leaf port-num {
      type uint16;
      description
        "Port number of the local (actor) aggregation member";
    }

    leaf partner-port-num {
      type uint16;
      description
        "Port number of the partner (remote) port for this member
        port";
    }

    leaf lacp-port-priority {
      if-feature srl_nokia-feat:lacp-fallback;
      type uint16;
      description
        "Configure the port priority for LACP.  This value is used to  determine which port should be activated with LACP fallback mode. Lower values are more preferred.";
    }

  }

	grouping lag-lacp-members-statistics {
    description
      "LACP packet statistics for the member interfaces";

    container statistics {
      description
        "LACP protocol counters";

      leaf lacp-in-pkts {
        type srl_nokia-comm:zero-based-counter64;
        description
          "Number of LACPDUs received";
      }

      leaf lacp-out-pkts {
        type srl_nokia-comm:zero-based-counter64;
        description
          "Number of LACPDUs transmitted";
      }

      leaf lacp-rx-errors {
        type srl_nokia-comm:zero-based-counter64;
        description
          "Number of LACPDU receive packet errors";
      }

      leaf lacp-tx-errors {
        type srl_nokia-comm:zero-based-counter64;
        description
          "Number of LACPDU transmit packet errors";
      }

      leaf lacp-unknown-errors {
        type srl_nokia-comm:zero-based-counter64;
        description
          "Number of LACPDU unknown packet errors";
      }

      leaf lacp-errors {
        type srl_nokia-comm:zero-based-counter64;
        description
          "Number of LACPDU illegal packet errors";
      }
    }
  } 
	
	augment "/srl_nokia-if:interface/srl_nokia-if-lag:lag/srl_nokia-if-lag:members" {
    uses lag-lacp-members-state;
  }
	augment "/srl_nokia-if:interface/srl_nokia-if-lag:lag/srl_nokia-if-lag:members" {
    uses lag-lacp-members-statistics;
  }

	grouping lacp-system-config {
		description
      "System level Configuration parameters for LACP";
      
    container lacp {
        if-feature "srl_nokia-feat:lag";
    	leaf system-priority {
				type uint16;
				description
					"Sytem priority used by the node on this LAG interface.
					Lower value is higher priority for determining which node
					is the controlling system.";
			}
			leaf system-id {
				type srl_nokia-comm:mac-address;
				description
					"The MAC address portion of the node's System ID. This is
					combined with the system priority to construct the 8-octet
					system-id";
			}
    }
	}
	augment "/srl_nokia-system:system" {
   	uses lacp-system-config;
	}

	grouping lag-lacp-config {
    description
      "Configuration parameters for LACP interfaces";

		container lacp{
                    presence "Enable LACP configuration";
                    must "../srl_nokia-if-lag:lag-type = 'lacp'" {
                        error-message "lacp container can only be configured when lag-type is lacp";
                    }
			description
				"LACP parameters for the associated LAG";
				
			leaf interval {
      	type lacp-period-type;
      	default SLOW;
      	description
        	"Set the period between LACP messages -- uses
        	the lacp-period-type enumeration.";
    	}

    	leaf lacp-mode {
      	type lacp-activity-type;
      	default ACTIVE;
      	description
					"ACTIVE is to initiate the transmission of LACP packets.
					 PASSIVE is to wait for peer to initiate the transmission of
					 LACP packets.";

			}

			leaf admin-key {
			  description
			    "Configure the LACP admin-key to be advertised by the local system.
			    If this value is not specified a value starting from 32768 is automatically 
			    assigned by the system.";
                            type uint16 {
                                range "1..65535";
                            }
			}

			leaf system-id-mac {
				type srl_nokia-comm:mac-address;
				description
					"The MAC address portion of the node's System ID. This is
					combined with the system priority to construct the 8-octet
					system-id.
					If not configured, the system-ID configured at the system/ level is used.";
			}
			leaf system-priority {
				type uint16;
				description
					"Sytem priority used by the node on this LAG interface.
					Lower value is higher priority for determining which node
					is the controlling system.
					If not configured, the system-priority configured at the system/ level is used.";
			}
		}
  }
	augment "/srl_nokia-if:interface/srl_nokia-if-lag:lag"  {
    uses lag-lacp-config;
  }

}
