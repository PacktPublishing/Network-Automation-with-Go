module srl_nokia-tools-configuration {
  yang-version 1.1;
  namespace "urn:srl_nokia/tools-configuration";
  prefix srl-tools-config;

  import srl_nokia-tools-system {
    prefix srl_nokia-tools-system;
  }
  import srl_nokia-common {
    prefix srl-comm;
  }
  import srl_nokia-extensions {
    prefix srl-ext;
  }

  description
    "This module defines operational commands related to the system configuration.";

  revision 2020-06-30 {
    description
      "SRLinux 20.6.1";
  }
  revision 2019-11-30 {
    description
      "SRLinux 19.11.1";
  }

  grouping configuration-tools-candidates-top {
    description
      "Operational commands related to configuration candidates";
    list candidate {
      srl-ext:first-released "20.6.1";
      description
        "List of configuration candidates currently active";
      key "name";
      leaf name {
        type srl-comm:name;
        description
          "The name of the candidate";
      }
      leaf clear {
        type empty;
        description
          "Clear the candidate from the system, discarding any changes

          This results in any users currently in the candidate being dropped back to running mode.";
      }
    }
  }

  grouping configuration-tools-sessions-top {
    description
      "Operational commands related to configuration sessions";
    list session {
      description
        "List of configuration sessions currently active";
      key "id";
      leaf id {
        type uint32;
        description
          "System generated ID for the configuration session";
      }
      leaf clear {
        type empty;
        description
          "Clear the session from the system, discarding any changes";
      }
    }
  }

  grouping configuration-tools-checkpoints-top {
    description
      "Operational commands related to checkpoints";
    list checkpoint {
      description
        "List of current checkpoints present in the system";
      key "id";
      leaf id {
        type union {
          type uint8;
          type srl-comm:checkpoint-name;
        }
        description
          "System generated ID, or operator defined name for the checkpoint";
      }
      leaf clear {
        type empty;
        description
          "Clear the checkpoint from the system";
      }
      leaf load {
        type empty;
        description
          "Load candidate from saved checkpoint configuration";
      }
      leaf revert {
        type empty;
        description
          "Revert running system configuration to the saved checkpoint configuration

           This functions as a load and commit action.";
      }
    }
    container generate-checkpoint {
      presence "Generate checkpoint";
      description
        "Generate a checkpoint point based on the current running configuration";
      leaf name {
        type srl-comm:checkpoint-name;
        description
          "User provided name of the checkpoint";
      }
      leaf comment {
        type string;
        description
          "User provided comment to associate with the checkpoint";
      }
    }
    leaf confirmed-accept {
        srl-ext:first-released "20.6.1";
        type empty;
        description
          "Accepts an in progress commit and stops the confirmation timer";
    }
    leaf confirmed-reject {
        srl-ext:first-released "20.6.1";
        type empty;
        description
          "Rejects an in progress commit and stops the confirmation timer";
    }
  }

  grouping configuration-top {
    container configuration {
      presence "Configure tools system configuration";
      description
        "Top-level container for operational commands related to the system configuration";
      leaf save {
        type empty;
        description
          "Save current running configuration as initial (startup) configuration - config.json";
      }
      leaf rescue-save {
        type empty;
        description
          "Save current running configuration as rescue configuration - rescue-config.json";
      }
      leaf rescue-clear {
        type empty;
        description
          "Remove rescue configuration";
      }
      uses configuration-tools-checkpoints-top;
      uses configuration-tools-sessions-top;
      uses configuration-tools-candidates-top;
    }
  }

  augment "/srl_nokia-tools-system:system" {
    srl-ext:first-released "19.11.1";
    uses configuration-top;
  }
}
