module srl_nokia-mpls {

    yang-version 1.1;

    // namespace
    namespace "urn:srl_nokia/mpls";

    prefix "srl_nokia-mpls";

    import srl_nokia-common { prefix srl_nokia-comm; }
    import srl_nokia-network-instance { prefix srl_nokia-netinst; }
    import srl_nokia-next-hop-groups { prefix srl_nokia-nhg; }
    import srl_nokia-features { prefix srl-feat; }
    import srl_nokia-system { prefix srl_nokia-system; }
    import srl_nokia-mpls-label-management { prefix srl_nokia-mplslbl; }

    description
        "This yang file adds support for basic MPLS configuration and state at the network instance level.";

  revision 2021-06-30 {
    description
      "SRLinux 21.6.1";
  }
  revision 2021-03-31 {
    description
      "SRLinux 21.3.1";
  }
  revision 2020-06-30 {
    description
      "SRLinux 20.6.1";
  }
  revision 2019-11-30 {
    description
      "SRLinux 19.11.1";
  }

    grouping mpls-top {
        container mpls {
            if-feature "srl-feat:jericho2";
            must "current()/../srl_nokia-netinst:type = 'srl_nokia-netinst:default'" {
                error-message "MPLS configuration only supported with network instance type default";
            }
            presence "Configure MPLS";
            leaf admin-state {
                type srl_nokia-comm:admin-state;
                default "disable";
                description
                    "Adminstratively enable or disable MPLS.

                    When MPLS is enabled, MPLS packets can be received on any subinterface of the default network-instance. When MPLS is disabled, MPLS packets are discarded if received on any subinterface of the default network-instance.";
            }
            leaf static-label-block {
                if-feature srl-feat:label-management;
                type leafref {
                    path "/srl_nokia-system:system/srl_nokia-mplslbl:mpls/srl_nokia-mplslbl:label-ranges/srl_nokia-mplslbl:static/srl_nokia-mplslbl:name";
                }
                must "not(/srl_nokia-system:system/srl_nokia-mplslbl:mpls/srl_nokia-mplslbl:label-ranges/srl_nokia-mplslbl:static[srl_nokia-mplslbl:name=current()]/srl_nokia-mplslbl:shared)" {
                    error-message "Static label block for MPLS should be exclusive (not shared)";
                }
            }
            leaf static-label-block-status {
                config false;
                if-feature srl-feat:label-management;
                type enumeration {
                    enum "available";
                    enum "unavailable";
                }
                description
                    "Status of the label block.
          
                    The label block may show as unavailable if there is pending cleanup.";
            }
            list static-entry {
                key "top-label preference";
                leaf top-label {
                    type srl_nokia-comm:mpls-label;
                    description
                        "A received MPLS packet, received on any subinterface, matches this static entry if its top label stack entry contains the label value specified by this leaf.";
                    // akimana todo: include IMPLICIT_NULL into label validation (maybe using int(current()) < 5))???
                    must "(current() >= /srl_nokia-system:system/srl_nokia-mplslbl:mpls/srl_nokia-mplslbl:label-ranges/srl_nokia-mplslbl:static[srl_nokia-mplslbl:name=current()/../../static-label-block]/srl_nokia-mplslbl:start-label)"
                    + " and (current() <= /srl_nokia-system:system/srl_nokia-mplslbl:mpls/srl_nokia-mplslbl:label-ranges/srl_nokia-mplslbl:static[srl_nokia-mplslbl:name=current()/../../static-label-block]/srl_nokia-mplslbl:end-label)" {
                        error-message "static-label-block is not configured or top-label is out of static-label-block's range";
                    }
                }
                leaf preference {
                    type uint8 {
                        range "0..255";
                    }
                    description
                        "For a given top label value the entry with the lowest preference is selected as the active entry";
                }
                leaf admin-state {
                    type srl_nokia-comm:admin-state;
                    default "enable";
                    description
                        "Used to disable the entire static route and all its next-hops.";
                }
                leaf operation {
                    type enumeration {
                      enum pop  { value 1; }
                      enum swap { value 2; }
                    }
                    default swap;
                    description
                        "The operation to be performed with the top label.";
                }
                leaf collect-stats {
                    type boolean;
                    default false;
                    description
                        "When set to true, stats resources are used to count the number of incoming packets matching the top label value of this static MPLS route";
                }
                leaf installed {
                    config false;
                    type boolean;
                    description
                      "Indicates whether the MPLS route entry was programmed in the data path.";
                }
                leaf next-hop-group {
                    type leafref {
                        path "../../../srl_nokia-nhg:next-hop-groups/srl_nokia-nhg:group/srl_nokia-nhg:name";
                    }
                }
            }
        }
    }
    augment "/srl_nokia-netinst:network-instance" {
        uses mpls-top;
    }
}
