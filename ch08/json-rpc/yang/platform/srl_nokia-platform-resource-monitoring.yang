module srl_nokia-platform-resource-monitoring {
  yang-version 1.1;
  namespace "urn:srl_nokia/platform-res-monitor";
  prefix srl_nokia-platform-res-monitor;

  import srl_nokia-platform {prefix srl_nokia-platform; }

  description
    "This module defines configuration and operational data for system-wide monitoring of critical resources";

  revision 2019-11-30 {
    description
      "SRLinux 19.11.1";
  }

  augment "/srl_nokia-platform:platform" {
      container resource-monitoring {
      }
  }
}
